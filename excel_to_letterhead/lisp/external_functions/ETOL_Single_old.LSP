; ██╗███╗   ███╗██████╗  ██████╗ ██████╗ ████████╗
; ██║████╗ ████║██╔══██╗██╔═══██╗██╔══██╗╚══██╔══╝
; ██║██╔████╔██║██████╔╝██║   ██║██████╔╝   ██║   
; ██║██║╚██╔╝██║██╔═══╝ ██║   ██║██╔══██╗   ██║   
; ██║██║ ╚═╝ ██║██║     ╚██████╔╝██║  ██║   ██║   
; ╚═╝╚═╝     ╚═╝╚═╝      ╚═════╝ ╚═╝  ╚═╝   ╚═╝    

(vl-load-com)


; ███████╗██╗   ██╗███╗   ██╗ ██████╗████████╗██╗ ██████╗ ███╗   ██╗███████╗
; ██╔════╝██║   ██║████╗  ██║██╔════╝╚══██╔══╝██║██╔═══██╗████╗  ██║██╔════╝
; █████╗  ██║   ██║██╔██╗ ██║██║        ██║   ██║██║   ██║██╔██╗ ██║███████╗
; ██╔══╝  ██║   ██║██║╚██╗██║██║        ██║   ██║██║   ██║██║╚██╗██║╚════██║
; ██║     ╚██████╔╝██║ ╚████║╚██████╗   ██║   ██║╚██████╔╝██║ ╚████║███████║
; ╚═╝      ╚═════╝ ╚═╝  ╚═══╝ ╚═════╝   ╚═╝   ╚═╝ ╚═════╝ ╚═╝  ╚═══╝╚══════╝

(defun get-active-doc nil
    (cond ( acdoc ) ((setq acdoc (vla-get-activedocument (vlax-get-acad-object)))))
  )
;------------------------------------------------------------------------------------------------------------

(defun get-remote-doc (file-path)
  (setq doc (vla-open (vla-get-documents (vlax-get-acad-object)) file-path )) 
  )

;------------------------------------------------------------------------------------------------------------

(defun modelspacer (doc)
       (vla-get-modelspace doc))

;------------------------------------------------------------------------------------------------------------

(defun paperspacer (doc)
       (vla-get-paperspace doc))

;------------------------------------------------------------------------------------------------------------

(defun number_of_docs ()
  (setq acad* (vlax-get-acad-object));_ the acad program
  (setq documents (vla-get-Documents acad*));_ all documents collection
  (progn
  (setq docs-open (vla-get-count documents));_ opened dwgs
  )
  )

;------------------------------------------------------------------------------------------------------------

(defun close_others()
    ;; This example cycles through the documents collection
    ;; and closes all open drawings using the Close method
    ;; except the current drawing.
    (setq acadObj (vlax-get-acad-object))
    (setq curDoc (vla-get-ActiveDocument acadObj))
    (setq docs (vla-get-Documents acadObj))

    ;; Close all open documents and discard changes, except for the current drawing
    (vlax-for doc docs
        (if (/= (vla-get-Name doc) (vla-get-Name curDoc))
	    (progn
                (vla-Close doc :vlax-true)
	    )
        )
    )
  )

;------------------------------------------------------------------------------------------------------------

(defun delay_it ( msec )
 (
   (lambda ( start )
     (while (< (- (getvar 'MILLISECS) start) msec))
   )
   (getvar 'MILLISECS)
 )
  )

;------------------------------------------------------------------------------------------------------------

(defun LM:readcsv ( csv / des lst sep str )
    (if (setq des (open csv "r"))
        (progn
            (setq sep (cond ((vl-registry-read "HKEY_CURRENT_USER\\Control Panel\\International" "sList")) (",")))
            (while (setq str (read-line des))
                (setq lst (cons (LM:csv->lst str sep 0) lst))
            )
            (close des)
        )
    )
    (reverse lst)
  )

;------------------------------------------------------------------------------------------------------------

(defun LM:csv->lst ( str sep pos / s )
    (cond
        (   (not (setq pos (vl-string-search sep str pos)))
            (if (wcmatch str "\"*\"")
                (list (LM:csv-replacequotes (substr str 2 (- (strlen str) 2))))
                (list str)
            )
        )
        (   (or (wcmatch (setq s (substr str 1 pos)) "\"*[~\"]")
                (and (wcmatch s "~*[~\"]*") (= 1 (logand 1 pos)))
            )
            (LM:csv->lst str sep (+ pos 2))
        )
        (   (wcmatch s "\"*\"")
            (cons
                (LM:csv-replacequotes (substr str 2 (- pos 2)))
                (LM:csv->lst (substr str (+ pos 2)) sep 0)
            )
        )
        (   (cons s (LM:csv->lst (substr str (+ pos 2)) sep 0)))
    )
  )

;------------------------------------------------------------------------------------------------------------

(defun LM:csv-replacequotes ( str / pos )
    (setq pos 0)
    (while (setq pos (vl-string-search  "\"\"" str pos))
        (setq str (vl-string-subst "\"" "\"\"" str pos)
              pos (1+ pos)
        )
    )
    str
  )

;------------------------------------------------------------------------------------------------------------

(defun change_it_old (old new) ;ESKİ VERSİYON
	(setq OldTxt old
		  NewTxt new)
	
	(setq ss (ssget "x" '((0 . "TEXT,MTEXT"))))
	
	(setq i (sslength ss))
	
	(while (not (minusp (setq i (1- i))))
		(setq oText (vlax-ename->vla-object (ssname ss i)))
		(setq Txt (vlax-get-property oText 'TextString))
		
		(if (vl-string-search OldTxt txt)
			(progn
				(setq newChg (vl-string-subst NewTxt OldTxt txt))
				(vlax-put-property oText 'TextString newchg)
				(vlax-invoke-method oText 'Update)
			)
		)
	)
	(princ)
  )

;-----------------------------------------------------------------------------------------------------------

;THIS FUNCTION GETS ALL THE OBJECTS IN THE MODELSPACE AND CHECKS IF THE OBJECT WHETHER TEXT OR NOT. 
(defun change_it (OldTxt NewTxt doc / errobj) 
  (setq modelspace (modelspacer doc))
  (vlax-for entry modelspace 
    (setq errobj (vl-catch-all-apply 
                   '(lambda () 

                        (if 
                          (or (eq (vla-get-objectname entry) "AcDbMText") 
                              (eq (vla-get-objectname entry) "AcDbText")
                          )
                          (progn 
                              (setq txt (vlax-get-property entry 'TextString))
                              (if (eq (vla-get-textstring entry) OldTxt)
                                (progn 
                                  (vlax-put-property entry 'TextString NewTxt)
                                  (vlax-invoke-method entry 'Update)
                                )
                              )
                            
                          )
                        )
                      
                    )
                 )
    )
    (if (vl-catch-all-error-p errobj) 
      (progn 
        (princ)
      )
      (print entry)
    )
    (princ)
  )
  )

;-----------------------------------------------------------------------------------------------------------

(defun LM:StringWrap ( str len / pos )
    (if (< len (strlen str))
        (cons
            (substr str 1
                (cond
                    (   (setq pos (vl-string-position 32 (substr str 1 len) nil t)))
                    (   (setq pos (1- len)) len)
                )
            )
            (LM:StringWrap (substr str (+ 2 pos)) len)
        )
        (list str)
    )
  )

;-----------------------------------------------------------------------------------------------------------

(defun LM:lst->str ( lst del )
    (if (cdr lst)
        (strcat (car lst) del (LM:lst->str (cdr lst) del))
        (car lst)
    )
  )

;-----------------------------------------------------------------------------------------------------------

(defun replace_all_text ()
      (foreach line csv_data 
        (setq pafta_no (nth 0 line)) ;Gets the first column to get the file name
        (if (= (car line) file_name) ;Gets the line where the filename matches.
          (progn
        
            (change_it "QDT" (nth 2 line))  ;DATE       QDT
            (change_it "QSC" (nth 3 line))  ;SCALE      QSC
            (change_it "QFM" (nth 4 line))  ;FORMAT     QFM
            (change_it "QAE" (nth 8 line))  ;AREA       QAE
            (change_it "QSAE" (nth 9 line)) ;SUBAREA    QSAE
            (change_it "QSY" (nth 10 line)) ;SYSTEM     QSY
            (change_it "QSSY" (nth 11 line));SUBSYSTEM  QSSY
            (change_it "QLN" (nth 12 line)) ;LANGUAGE   QLN
            (change_it "QDCT" (nth 13 line));DOCTYPE    QDCT
            (change_it "QDCN" (nth 14 line));DOCNO      QDCN
            (setq pafta_no_wrap (LM:StringWrap (nth 0 line) 1)) 
            (setq pafta_no_check (strcat (car pafta_no_wrap) (cadr pafta_no_wrap)))
            (setq new_pafta_name (LM:lst->str (cdr (cddddr line)) "-") )
            ; (if (= pafta_no_check project_code) 
            ;   (progn

            ;     (setq thisdrawing 
            ;       (vla-get-activedocument 
            ;             (vlax-get-acad-object)))
            ;     (setq import (strcat import_path pafta_no ".dwg"))
            ;     (setq export (strcat export_path new_pafta_name ".dwg"))
            ;     (vla-saveas thisdrawing export ac2018_dwg)
            ;     ; (vla-close thisdrawing :vlax-true)
            ;     ; ; (vl-file-copy import export T) ;SAVE REFERENCE AS EXPORT
            ;     )
            ;   )            
            )
          )
        ) 
      )



;-----------------------------------------------------------------------------------------------------------


; ██╗   ██╗ █████╗ ██████╗ ██╗ █████╗ ██████╗ ██╗     ███████╗███████╗
; ██║   ██║██╔══██╗██╔══██╗██║██╔══██╗██╔══██╗██║     ██╔════╝██╔════╝
; ██║   ██║███████║██████╔╝██║███████║██████╔╝██║     █████╗  ███████╗
; ╚██╗ ██╔╝██╔══██║██╔══██╗██║██╔══██║██╔══██╗██║     ██╔══╝  ╚════██║
;  ╚████╔╝ ██║  ██║██║  ██║██║██║  ██║██████╔╝███████╗███████╗███████║
;   ╚═══╝  ╚═╝  ╚═╝╚═╝  ╚═╝╚═╝╚═╝  ╚═╝╚═════╝ ╚══════╝╚══════╝╚══════╝

(setq doc (get-active-doc))
(setq modelspace (vla-get-modelspace (get-active-doc)))
(setq csv_file "C:/Users/BAHA-LAPTOP/Documents/GitHub/tekfenRandomStudies/excel_to_letterhead/documents/ANTET-VARIABLES-V2.csv")
(setq csv_data (LM:readcsv csv_file)) ;WHOLE TABLE
(setq project_code "M7")
(setq file_name (vl-filename-base (getvar "dwgname")) )
(setq import_path "C:/Users/BAHA-LAPTOP/Documents/GitHub/tekfenRandomStudies/excel_to_letterhead/documents/IMPORT_ANTET/")
(setq export_path "C:/Users/BAHA-LAPTOP/Documents/GitHub/tekfenRandomStudies/excel_to_letterhead/documents/EXPORT_ANTET/")
(setq remote_file "C:/Users/BAHA-LAPTOP/Documents/GitHub/tekfenRandomStudies/excel_to_letterhead/documents/IMPORT_ANTET/REMOTE_TEST.dwg")


; ███╗   ███╗ █████╗ ██╗███╗   ██╗
; ████╗ ████║██╔══██╗██║████╗  ██║
; ██╔████╔██║███████║██║██╔██╗ ██║
; ██║╚██╔╝██║██╔══██║██║██║╚██╗██║
; ██║ ╚═╝ ██║██║  ██║██║██║ ╚████║
; ╚═╝     ╚═╝╚═╝  ╚═╝╚═╝╚═╝  ╚═══╝

(defun c:test1 ( / )

    (LM:ODBX
        (function
            (lambda ( doc )
                
                (replace_all_text)
            )
        )
        nil t
    )
    (princ)
  )


(defun analyzer (OldTxt NewTxt) 
(vlax-for layout (vla-get-layouts (get-active-doc))
  (vlax-for entry	(vla-get-block layout)
    
    (if 
      (or (eq (vla-get-objectname entry) "AcDbMText") 
          (eq (vla-get-objectname entry) "AcDbText")
      )
      
      (progn
          
           (setq txt (vlax-get-property entry 'TextString))
            
           (if (eq (vla-get-textstring entry) OldTxt)
             (progn 
               (print (vla-get-textstring entry))
               (vlax-put-property entry 'TextString NewTxt)
               (vlax-invoke-method entry 'Update)
             )
           )
         
      )
    )
  )
  (princ)
  )
)

; (setq layout_number (vla-get-count (vla-get-layouts (get-active-doc))))
; (setq counter 0)
; (vlax-for layout (vla-get-layouts (get-active-doc))
;   (vlax-for entry	(vla-get-block layout)
    
;   )
; )

vla-put-activespace
vla-get-paperspace
